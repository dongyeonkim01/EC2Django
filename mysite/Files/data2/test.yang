module qucell-o1-interface {
  yang-version 1.1;
  namespace "urn:qucell:o1-interface:1.0";
  prefix "qucell-o1-int";
  
  import ietf-interfaces {
    prefix "if";
  }
    
  import ietf-netconf-acm {
    prefix nacm;
    reference
      "RFC 8341: Network Configuration Access Control Model";
  }
  
  import ietf-inet-types {
    prefix inet;
  }
  
  organization
    "Qucell Networks Co., Ltd.";
	
  contact
    "";
	
  description
    "This modules contains YANG definitions for O1 interface.";
    
  revision 2020-04-27 {
    description
	  "Initial revision";
  }
     
  grouping ves-listener-config {
    description
	  "A reusable grouping for VES listener configuration";
	  
    leaf server-root {
	  type inet:uri;
	  mandatory true;
		description
		  "Server root of VES listener. ServerRoot = https://{Domain|IP}:{Port}/{optionalRoutingPath}";
	  }
		
	leaf username {
	  nacm:default-deny-write;
	  type string;
	  description
	    "The username for the HTTP basic authentication.";
	}
		
	leaf password {
	  nacm:default-deny-all;
	  type string;
	  description
	    "The password for the HTTP basic authenticaiton.";
	}

	container tls-client-config {
	  nacm:default-deny-write;
	  description
	    "Nodes for TLS client configuration.
		Currently configuration for mutual authentication is specified. Nodes for TLS hello parameters configuration (TLS version, cipher suites) may be added in the future.";
	  
	  container client-identity {
	    description
		  "Specifies certificate and corresponding private key used to identify TLS client";
		
		leaf certificate {
		  type string;
		  description
		    "Identifier or reference for a specific certificate in the device";
		}
		  
		leaf private-key {
		  type string;
		  description
		    "Identifier or reference for a specific private key in the decive";
		}
	  }
	  
	  leaf-list ca-certs {
	    type string;
	    description
		  "Identifier or reference for the certificate authority (CA) certificates used by the TLS client to authenticate TLS server certificates. A server certificate is authenticated if it has a valid chain of trust to a configured CA certificate.";
	  }
	}
  }
  
  container o1-interface {
    description
	  "Nodes for O1 interface";

	container nf-info {
	  description
	    "Nodes for NF information";
	  
	  leaf nf-type {
		type enumeration {
		  enum Cu {
		    description
			  "Indicates type of this NF is CU.";
		  }
		  enum Du {
		    description
			  "Indicates type of this NF is DU.";
		  }
		}
		config false;
		mandatory true;
		description
		  "NF type e.g. CU, DU. The value of this leaf is used for NfName which is one of subfields of PublisherName in VES eventName.";
	  }
	
	  leaf nf-id {
		type string;
		config false;
		mandatory true;
	    description
	      "Unique identifer for each NFs. The value of this leaf is used for reportingEntityName and sourceName in VES commonEventHeader.";
	  }
	  
	  leaf dn {
	    type string;
		description
		  "Distinguished Name of NF. DN is used to identify managed element(NF) in 3GPP MnS.";
	  }
	  
	  leaf service-configuration {
		type enumeration {
		  enum need-to-configure {
		    description
			  "Indicates PNF needs service configuration to initiate service.
			  PNF sends pnfRegistration event periodically until service configuration is done. In this case, PNF stays in the unregistered state.";
		  }
		  enum done {
		    description
			  "Indicates service configuration from the EMS has been finished. PNF moves to the registered state.";
		  }
		}
		description
		  "Indicates service configuration from the EMS is done or not.";
	  }
	  
	  leaf registration-state {
		type enumeration {
		  enum unregistered {
		    description
			  "PNF is in unregistered state.
			  In unregistered state, only pnfRegistration event is transmitted.";
		  }
		  enum registered {
		    description
			  "PNF is in registered state.
			  The events except pnfRegistration are transmitted only when PNF is in registered state.";
		  }
		}
		config false;
		description
		  "Registration state of PNF";
	  }

	  leaf local-endpoint {
	    type union {
		  type leafref {
		    path "/if:interfaces/if:interface/if:name";
	      }
		  type inet:ip-address;
		}
		description
		  "The local interface/IP address to bind for when connecting to the VES listener.
		  If this leaf is not configured, it is automatically configured based on the DHCP server which provided the VES listener discovery.";
	  }
	}
	
	container ves-listeners {
	  description
	    "Nodes for VES listeners";
	
	  leaf active-listener {
		type enumeration {
		  enum primary {
		    description
			  "Indicates current active listner is primary VES listener.";
		  }
		  enum secondary {
		    description
			  "Indicats current active listner is secondary VES listener.";
		  }
		  enum none {
		    description
			  "Indicates both primary and secondary listener are disconnected.
			  The PNF tries to send pnfRegistaration to the VES listener.";
		  }
		}
		config false;
		description
		  "Indicates current active VES listener. The VES event is transfered to the active listener.";
	  }
	  
	  container primary-ves-listener {
	    presence
		  "Indicates that the NF supports communication with VES listener.";
	    description
		  "Nodes for primary VES listener";
		uses ves-listener-config;
	  }
	  
	  container secondary-ves-listener {
	    presence
		  "Indicates that the NF supports switch over to the secondary VES listener for the case when the primary VES listener is not available.";
	    description
		  "Nodes for secondary VES listener";
		uses ves-listener-config;
	  }
	}
	
	container ves-retry-policy {
	  description
	    "Nodes for VES event retransmission policy";
		
	  leaf pnf-reg-timer {
	    type uint16 {
		  range "1..max";
		}
		units minutes;
		default 5;
		description
		  "This timer is triggered when the PNF registration is initiated. After successful PNF registration this timer is stopped.
		  If PNF registration is not completeted until this timer is exhausted, the PNF restarts PNF registration, and the timer starts again. For the successful PNF registration, this timer shall be have enough time interval.";
	  }
	  
	  leaf heartbeat-period {
		type uint16;
		units seconds;
		default 60;
		description
		  "Period of heartbeat notification emission. The value of zero has the special meaning of stopping the heartbeat notification emission.";
      }
	  
	  container event-retransmission {
	    description
		  "Specifies configuration about event retransmission.";
		  
	    leaf ack-timeout {
	      type uint16 {
		    range "1..max";
		  }
		  units seconds;
		  default 5;
		  description
		    "Time interval that NF waits the response from the VES listener";
	    }
	  
	    leaf max-attempts {
	      type uint16;
		  default 3;
		  description
		    "Max retry number for event re-transmission";
	    }
	  
	    leaf retry-interval {
	      type uint16 {
		    range "1..max";
		  }
		  units seconds;
		  default 5;
		  description
		    "Failed event is retransmitted after waiting for the time configured by this leaf.";
	    }
	  }
	}
	
	container ves-event-buffer {
	  description
	    "Nodes for buffer configuration";
		
	  leaf max-buffered-time {
	    type uint16;
		units minutes;
		default 60;
		description
		  "Indicates maximum period that events are queued. The event exceeded this time limit is discarded.";
	  }
	  
	  leaf max-buffered-events {
	    type uint16;
		description
		  "Indicates maximum number of events that buffer can save. If the buffer is exceeded this limit, the oldest event is discarded in the manner of FIFO (First In First Out).";
	  }
	}
  }
}
